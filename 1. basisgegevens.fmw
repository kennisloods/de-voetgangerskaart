FME workspace 1. basisgegevens.fmw

Parameters:
- P_BRON_WEGDELEN = K:\GEODATA\Themadata\BOR\Data\SHP\Wegvakonderdelen.shp   # Source Esri Shapefile(s)
- P_VOETGANGERS = K:\GEODATA\Kennisloods\Data\Voetgangerskaart\Voetgangerskaart_basisgegevens.gpkg   # GeoPackage File
- P_LOG = $(FME_MF_DIR)log\1. basisgegevens.log   # Log File

Readers:
- ESRISHAPE_1: ESRISHAPE from $(P_BRON_WEGDELEN) in EPSG:28992

Writers:
- GEOPACKAGE_1: GEOPACKAGE to $(P_VOETGANGERS) in EPSG:28992

Wegvakonderdelen (reader ESRISHAPE_1)
    attributes: BEHEEROBJE char(98), AANLEGJAAR long, AMBITIENIV char(200), BEGINPUNT char(80), BEHEERDER char(50), BESTEMMING char(50), BORNAME char(25), BOVENSTE_V char(50), BOVENSTE00 char(3), BREEDTE long, BUURT char(80), CLUSTERNUM long, DIKTEFUNDE long, EIGENAAR char(80), EINDPUNT char(80), EXTRA_INFO char(200), EXTRA_IN00 char(200), EXTRA_IN01 char(200), FUNDERING char(50), GEBRUIKSFU char(50), GEMEENTE char(80), ID long, INDICATIE_ char(3), LAAG_DIKTE long, LAATSTE_MU date, LENGTE long, LIGGING char(22), ONDERDEELN long, ONDERDEELT char(50), ONDERGROND char(50),
      OPPERVLAKT long, STRAAT char(80), STRAATCODE char(16), STRUCTUURG char(80), VERHARDING char(250), VOEGLENGTE long, VOEGTYPE char(50), WEGTYPE char(200), WEGVAKNUMM long, WIJK char(80)
    -> CoordinateRounder_BOR
Note: De BGT is nu nog niet gebruikt omdat daar de openbareruimte-ids ontbreken. / De BOR bevat echter niet alle wegdelen in Rotterdam en ook geen hoogteniveaus. / Het streven is om uiteindelijk de BGT te gebruiken en daarbij de straatcodes te koppelen.
Note: voorkomens van KLASSE_IMG / (er is gefilterd op de vetgedukte waardes): / <Empty> / Begroeid terreindeel / Onbegroeid terreindeel / Overig bouwwerk / Gebouwinstallatie / Pand / Kunstwerkdeel / Scheiding / Ondersteunend waterdeel / Waterdeel / Ondersteunend wegdeel / Overbruggingsdeel / Wegdeel / Tunneldeel / Weginrichtingselement / Vegetatieobject / Ongeclassificeerd object
CoordinateRounder_BOR
    YPREC = 3
    XPREC = 3
    ZPREC = 0
    ROUNDED -> AttributeFilter
    ROUNDED -> AttributeKeeper_BOR_alles
AttributeFilter
    ATTR_NAME = ONDERDEELT
    ATTR_VALUES = <Empty>,<Missing>,<Null>,<Unfiltered>,Voetstraat         Even,Voetstraat       Midden,Voetstraat       Oneven,Voetstraat op trap
    Voetstraat Even -> AttributeKeeper_BOR
    Voetstraat Midden -> AttributeKeeper_BOR
    Voetstraat Oneven -> AttributeKeeper_BOR
    Voetstraat op trap -> AttributeKeeper_BOR
AttributeKeeper_BOR
    KEEP_ATTRS = LENGTE,STRAATCODE
    -> Dissolver_BOR
Note: dissolve per straatcode
Dissolver_BOR
    DEAGGREGATE_INPUT = Yes
    SUM = LENGTE
    CONNECT_Z_MODE = First Wins
    GROUP_BY = STRAATCODE
    ACCUM_INPUT_ATTRS = Use Attributes From One Feature
    NO_OVRLP = No
    AREA -> Counter_2
    <REJECTED> -> Junction_2
Note: uitdelen tijdelijke ID / tbv de featureMerger
Counter_2
    START = 0
    DOMAIN = counter
    CNT_ATTR = _trottoirID
    SCOPE = Global
    -> CenterPointReplacer
    -> FeatureMerger [REQUESTOR]
    <REJECTED> -> Junction_13
Junction_13
    -> Junction_14
Junction_2
    -> Junction_4
Note: voorkomens van FUNCTIE bij KLASSE_IMG 'Wegdeel / (er is gefilterd op de vetgedukte waardes. Oranje waardes zijn ter dsicussie): / ruiterpad / transitie / inrit / rijbaan autosnelweg / rijbaan autoweg / rijbaan lokale weg / rijbaan regionale weg / overweg / spoorbaan / OV-baan / fietspad / voetgangersgebied / voetpad / voetpad op trap / parkeervlak / baan voor vliegverkeer
AttributeKeeper_BOR_alles
    KEEP_ATTRS = STRAATCODE
    -> Dissolver_BOR_2
Note: dissolve per straatcode / De straatdelen worden / hier alleen gedissolved, / maar nog niet geaggregeerd
Dissolver_BOR_2
    DEAGGREGATE_INPUT = Yes
    CONNECT_Z_MODE = First Wins
    GROUP_BY = STRAATCODE
    ACCUM_INPUT_ATTRS = Use Attributes From One Feature
    NO_OVRLP = No
    AREA -> Counter
    <REJECTED> -> Junction
Note: uitdelen segmentID
Counter
    START = 0
    DOMAIN = counter
    CNT_ATTR = segmentID
    SCOPE = Global
    -> SpatialRelator [Supplier]
    -> wegdelen_agg (writer GEOPACKAGE_1)
    <REJECTED> -> Junction_9
Note: per straatcode + segmentID / aggregeren van de voetgangersdelen / en sommeren van de lengte
Aggregator
    MODE = Geometry - Assemble One Level
    ACCUM_ATTRS_NAME = Use Attributes From One Feature
    SEP = ,
    SUM = LENGTE
    GROUP_BY = segmentID STRAATCODE
    ORDERED = No
    AGGREGATE_TYPE = Homogeneous Collection (If Possible)
    AGGREGATE -> voetgangerswegdelen (writer GEOPACKAGE_1)
voetgangerswegdelen (writer GEOPACKAGE_1)
    attributes: STRAATCODE text(16), segmentID int, LENGTE int
Junction_9
    -> Junction_10
wegdelen_agg (writer GEOPACKAGE_1)
    attributes: STRAATCODE text(16), segmentID int
Junction
    -> Junction_3

Bookmark: ophalen segmentID
  Bij elk voetgangerswegdeel wordt bepaald van welk wegdeelsegment het deel uitmaakt. 
  Om de nauwkeurigheid en snelheid van het script te borgen wordt een vergelijking gemaakt op basis van een punt dat gegarandeerd binnen het voetgangerswegdeel ligt.
Note: Polygoon vervangen door een punt / dat gegarandeerd in die polygoon / ligt.
CenterPointReplacer
    MODE = Inside Point
    POINT -> SpatialRelator [Requestor]
    UNTOUCHED -> Junction_5
Junction_5
    -> Junction_6
SpatialRelator
    ATTR_ACCUM_MODE = Merge Supplier
    ATTR_CONFLICT_RES = Use Requestor
    SUCCESS_ATTR = _related_candidates
    LIST_ATTRS_TO_INCLUDE = segmentID
    AGGREGATE_HANDLING = Yes
    CURVE_BOUNDARY_RULE_PARAM = Default Rule
    GROUP_BY = STRAATCODE
    PREDICATES = WITHIN
    LIST_NAME = _relationships
    CALC_CARD = No
    -> AttributeRemover
    <Rejected> -> Junction_7
AttributeRemover
    REMOVE_ATTRS = _related_candidates
    LIST_ATTRS = _relationships{}
    -> FeatureMerger [SUPPLIER]
FeatureMerger
    ATTR_ACCUM_MODE = Merge Supplier
    ATTR_CONFLICT_RES = Use Requestor
    SUPPLIERS_FIRST = No
    REJECT_NULL_MISSING_KEYS = No
    MERGE_TYPE = Attributes Only
    IGNORE_NULLS = No
    PROCESS_DUPS = No
    JOIN_KEYS = @Value(_trottoirID) @Value(_trottoirID) AUTO
    MERGED -> AttributeRemover_2
    <REJECTED> -> Junction_11
AttributeRemover_2
    REMOVE_ATTRS = _trottoirID
    -> Aggregator
Junction_11
    -> Junction_12
Junction_7
    -> Junction_8

Bookmark: uitval
Junction_6
    -> _Rejected_
Junction_14
    -> _Rejected_
Junction_4
    -> _Rejected_
Junction_12
    -> _Rejected_
Junction_8
    -> _Rejected_
Junction_10
    -> _Rejected_
Junction_3
    -> _Rejected_
_Rejected_: Logger
    MESSAGE = Feature is:
    MAXCOORDS = 20
    MAXFEATS = 20
