FME workspace 2. indicatoren_per_voetgangerswegdeel.fmw

Parameters:
- P_BRON_VOETGANGERSBASIS = K:\GEODATA\Kennisloods\Data\Voetgangerskaart\Voetgangerskaart_basisgegevens.gpkg   # GeoPackage File
- P_BRON_ALB = K:\GEODATA\Basisdata\ALB\Data\SHP\ALB.shp   # Source Esri Shapefile(s)
- P_BRON_BOR_BOMEN = K:\GEODATA\Themadata\BOR\Data\SHP\Bomen.shp   # Source Esri Shapefile(s)
- P_BRON_BOR_BANKEN = K:\GEODATA\Themadata\BOR\Data\SHP\Banken.shp   # Source Esri Shapefile(s)
- P_DOEL_VOETGANGERS = K:\GEODATA\Kennisloods\Data\Voetgangerskaart\Voetgangerskaart_indicatoren.gpkg   # GeoPackage File
- P_BUFFER_VOORDEUREN = 10   # Buffer Amount
- P_BUFFER_BANKEN = 2   # Buffer Amount
- P_BUFFER_BOMEN = 2   # Buffer Amount
- P_LOG = $(FME_MF_DIR)log\2. indicatoren_per_voetgangerswegdeel.log   # Log File

Readers:
- GEOPACKAGE_1: GEOPACKAGE from $(P_BRON_VOETGANGERSBASIS) in EPSG:28992
- ESRISHAPE_1: ESRISHAPE from $(P_BRON_BOR_BOMEN) in EPSG:28992
- ESRISHAPE_2: ESRISHAPE from $(P_BRON_BOR_BANKEN) in EPSG:28992
- ESRISHAPE_3: ESRISHAPE from $(P_BRON_ALB) in EPSG:28992

Writers:
- GEOPACKAGE_2: GEOPACKAGE to $(P_DOEL_VOETGANGERS) in EPSG:28992

Note: wegdelen uit de BOR, / gedissolved en geagregeerd / naar straatcode + segment
wegdelen_agg (reader GEOPACKAGE_1)
    attributes: STRAATCODE text(16), segmentID int
    -> Bufferer_wegdelen_bomen
    -> Bufferer_wegdelen_voordeuren
    -> Bufferer_wegdelen_banken
Note: wegdelen uit de BOR met type / 'voetstraat', / gedissolved en geagregeerd / naar straatcode + segment
voetgangerswegdelen (reader GEOPACKAGE_1)
    attributes: STRAATCODE text(16), segmentID int, LENGTE int
    -> AttributeKeeper
    -> FeatureMerger_bomen [REQUESTOR]
AttributeKeeper
    KEEP_ATTRS = segmentID,STRAATCODE
    -> Stoepbreedtebepaler_360 [Area]
    -> Stoepbreedtebepaler_290 [Area]
    -> Stoepbreedtebepaler_220 [Area]
    -> Stoepbreedtebepaler_180 [Area]
    -> Stoepbreedtebepaler_090 [Area]
    -> Clipper_lt_090 [CLIPPEE]
AttributeCreator
    ATTR_TABLE:
      SET_TO aant_bomen_hm = @Evaluate((@Value(aant_bomen)/@Value(LENGTE))*100)
      SET_TO aant_banken_hm = @Evaluate((@Value(aant_banken)/@Value(LENGTE))*100)
      SET_TO aant_voordeuren_hm = @Evaluate((@Value(aant_voordeuren)/@Value(LENGTE))*100)
    -> AttributeRounder
AttributeRounder
    ROUND_TYPE = Nearest
    SRC_ATTRS = aant_voordeuren_hm aant_bomen_hm aant_banken_hm
    PLACES = 4
    -> voetgangerswegdelen_indicatoren (writer GEOPACKAGE_2)
    <REJECTED> -> Junction_23
Junction_23 [off]
    -> Junction_24

Bookmark: aantal bomen / m
Bufferer_wegdelen_bomen
    ANGLE = 22.5
    CORNER_STYLE = Round
    OFFSET = $(P_BUFFER_BOMEN)
    CAP_STYLE = Round
    BUFFERED -> PointOnAreaOverlayer [AREA]
    <REJECTED> -> Junction_39
Junction_39
    -> Junction_40
Bomen (reader ESRISHAPE_1)
    attributes: BEHEEROBJE char(30), AANLEGJAAR long, AANTAL long, UITVOERING char(30), AMBITIENIV char(30), BEGROTINGS char(30), BEHEERDER char(30), BEHEERGROE char(40), BESCHERMIN char(15), BESTEMMING char(30), BOOMBEELD char(25), BOOMSORTIM char(50), BOOMSORT00 char(50), BOOMSTATUS char(30), SUBBUURT char(30), CONDITIE char(25), DATUM_LAAT date, STAMDIAMET long, EIGENAAR char(30), NUMMMER char(10), JAAR_LAATS char(50), JAAR_VOLGE char(50), FASE char(50), FUNCTIE char(30), GEMEENTE char(30), GESLACHT char(30), GR_GEBIED char(30), GROOTTE char(25), HERSTELVER char(25), HOOGTE char(8),
      ID long, KROONDIAME long, LAATSTE_MU date, LIGGING char(20), OMGEVINGSR char(30), ONDERHOUDS char(30), ONTWIKKELI char(25), OPMERKINGE char(200), STAMLENGTE char(30), STRAAT char(50), STRAATCODE long, STRUCTUURG char(200), STRUCTUURN char(200), TAKVRIJE_Z char(30), TOEKOMSTIG char(50), TOEKOMST00 char(50), LEVENSDUUR char(200), BUURT char(30), WIJK char(30)
    -> AttributeKeeper_bomen
AttributeKeeper_bomen
    -> PointOnAreaOverlayer [POINT]
PointOnAreaOverlayer
    OV_ATTR = aant_bomen
    ATTR_ACCUM_MODE = Merge Incoming
    ATTR_CONFLICT_RES = Use Original
    POLYS_FIRST = NO
    DEAGGREGATE_INPUT = Yes
    AREA -> FeatureMerger_bomen [SUPPLIER]
    <REJECTED> -> Junction_21
FeatureMerger_bomen
    PROCESS_DUPS = No
    JOIN_KEYS = @Value(STRAATCODE) @Value(STRAATCODE) AUTO @Value(segmentID) @Value(segmentID) AUTO
    ATTR_ACCUM_MODE = Merge Supplier
    MERGE_TYPE = Attributes Only
    ATTR_CONFLICT_RES = Use Requestor
    SUPPLIERS_FIRST = No
    IGNORE_NULLS = No
    REJECT_NULL_MISSING_KEYS = No
    MERGED -> FeatureMerger_bomen_MERGED_-__AttributeCreator_bomen
    UNMERGED_REQUESTOR -> FeatureMerger_bomen_MERGED_-__AttributeCreator_bomen
    <REJECTED> -> Junction_45
FeatureMerger_bomen_MERGED_-__AttributeCreator_bomen: Junction
    -> FeatureMerger_banken [REQUESTOR]
Junction_45
    -> Junction_46
Junction_21
    -> Junction_22

Bookmark: uitval
Junction_40
    -> _Rejected_
Junction_44
    -> _Rejected_
Junction_42
    -> _Rejected_
Junction_2
    -> _Rejected_
Junction_20
    -> _Rejected_
Junction_4
    -> _Rejected_
Junction_18
    -> _Rejected_
Junction_6
    -> _Rejected_
Junction_16
    -> _Rejected_
Junction_8
    -> _Rejected_
Junction_14
    -> _Rejected_
Junction_10
    -> _Rejected_
Junction_12
    -> _Rejected_
Junction_46
    -> _Rejected_
Junction_22
    -> _Rejected_
Junction_50
    -> _Rejected_
Junction_36
    -> _Rejected_
Junction_24
    -> _Rejected_
Junction_48
    -> _Rejected_
Junction_34
    -> _Rejected_
_Rejected_: Logger
    MAXFEATS = 20
    MAXCOORDS = 20
    MESSAGE = Feature is:

Bookmark: aantal banken / m
Bufferer_wegdelen_banken
    ANGLE = 22.5
    CORNER_STYLE = Round
    OFFSET = $(P_BUFFER_BANKEN)
    CAP_STYLE = Round
    BUFFERED -> PointOnAreaOverlayer_2 [AREA]
    <REJECTED> -> Junction_43
Junction_43
    -> Junction_44
Banken (reader ESRISHAPE_2)
    attributes: BEHEEROBJE char(20), AMBITIENIV char(50), BEHEERDER char(50), BUURT char(50), EIGENAAR char(50), ID long, ONDERHOUDS char(50), PLAATSINGS date, SOORTTYPE char(50), STRAAT char(50), WIJK char(50)
    -> AttributeKeeper_banken
AttributeKeeper_banken
    -> PointOnAreaOverlayer_2 [POINT]
PointOnAreaOverlayer_2
    OV_ATTR = aant_banken
    ATTR_ACCUM_MODE = Merge Incoming
    ATTR_CONFLICT_RES = Use Original
    POLYS_FIRST = NO
    DEAGGREGATE_INPUT = Yes
    AREA -> FeatureMerger_banken [SUPPLIER]
    <REJECTED> -> Junction_35
FeatureMerger_banken
    PROCESS_DUPS = No
    JOIN_KEYS = @Value(STRAATCODE) @Value(STRAATCODE) AUTO @Value(segmentID) @Value(segmentID) AUTO
    ATTR_ACCUM_MODE = Merge Supplier
    MERGE_TYPE = Attributes Only
    ATTR_CONFLICT_RES = Use Requestor
    SUPPLIERS_FIRST = No
    IGNORE_NULLS = No
    REJECT_NULL_MISSING_KEYS = No
    MERGED -> FeatureMerger_banken_UNMERGED_REQUESTOR_-__FeatureMerger_voordeuren_REQUESTOR
    UNMERGED_REQUESTOR -> FeatureMerger_banken_UNMERGED_REQUESTOR_-__FeatureMerger_voordeuren_REQUESTOR
    <REJECTED> -> Junction_49
FeatureMerger_banken_UNMERGED_REQUESTOR_-__FeatureMerger_voordeuren_REQUESTOR: Junction
    -> FeatureMerger_voordeuren [REQUESTOR]
Junction_49
    -> Junction_50
Junction_35
    -> Junction_36

Bookmark: aantal voordeuren / m
Bufferer_wegdelen_voordeuren
    ANGLE = 22.5
    CORNER_STYLE = Round
    OFFSET = $(P_BUFFER_VOORDEUREN)
    CAP_STYLE = Round
    BUFFERED -> PointOnAreaOverlayer_3 [AREA]
    <REJECTED> -> Junction_41
Junction_41
    -> Junction_42
ALB (reader ESRISHAPE_3)
    attributes: STRAATNUMM long, STRAATNAAM char(50), STRAATN_ZK char(50), HUISNUMMER short, HUISLETTER char(1), NADER char(11), X number(31,15), Y number(31,15), GEBDNAAM char(50), GEBDCODE long, BUURTNAAM char(50), BUURTCODE long, POSTCODE char(6), ADRES_KORT char(75), PC_HSNR char(16), OBJ_TYPE char(3), OBJECT char(50), BESTEMMING char(55)
    -> AttributeKeeper_voordeuren
AttributeKeeper_voordeuren
    -> PointOnAreaOverlayer_3 [POINT]
PointOnAreaOverlayer_3
    OV_ATTR = aant_voordeuren
    ATTR_ACCUM_MODE = Merge Incoming
    ATTR_CONFLICT_RES = Use Original
    POLYS_FIRST = NO
    DEAGGREGATE_INPUT = Yes
    AREA -> FeatureMerger_voordeuren [SUPPLIER]
    <REJECTED> -> Junction_33
FeatureMerger_voordeuren
    PROCESS_DUPS = No
    JOIN_KEYS = @Value(STRAATCODE) @Value(STRAATCODE) AUTO @Value(segmentID) @Value(segmentID) AUTO
    ATTR_ACCUM_MODE = Merge Supplier
    MERGE_TYPE = Attributes Only
    ATTR_CONFLICT_RES = Use Requestor
    SUPPLIERS_FIRST = No
    IGNORE_NULLS = No
    REJECT_NULL_MISSING_KEYS = No
    MERGED -> FeatureMerger_voordeuren_UNMERGED_REQUESTOR_-__AttributeCreator
    UNMERGED_REQUESTOR -> FeatureMerger_voordeuren_UNMERGED_REQUESTOR_-__AttributeCreator
    <REJECTED> -> Junction_47
FeatureMerger_voordeuren_UNMERGED_REQUESTOR_-__AttributeCreator: Junction
    -> AttributeCreator
Junction_47
    -> Junction_48
Junction_33
    -> Junction_34

Bookmark: stoepbreedtes berekenen
Stoepbreedtebepaler_360
    GROUP_BY = segmentID STRAATCODE
    STOEPBREEDTE = 3.60
    Area -> AttributeCreator_gt_360
    Area -> Clipper_290-360 [CLIPPER]
    _Rejected_ -> Junction
Junction
    -> Junction_2
Stoepbreedtebepaler_290
    GROUP_BY = segmentID STRAATCODE
    STOEPBREEDTE = 2.90
    Area -> Clipper_290-360 [CLIPPEE]
    Area -> Clipper_220-290 [CLIPPER]
    _Rejected_ -> Junction_3
Junction_3
    -> Junction_4
Stoepbreedtebepaler_220
    GROUP_BY = segmentID STRAATCODE
    STOEPBREEDTE = 2.20
    Area -> Clipper_220-290 [CLIPPEE]
    Area -> Clipper_180-220 [CLIPPER]
    _Rejected_ -> Junction_5
Junction_5
    -> Junction_6
Stoepbreedtebepaler_180
    GROUP_BY = segmentID STRAATCODE
    STOEPBREEDTE = 1.80
    Area -> Clipper_180-220 [CLIPPEE]
    Area -> Clipper_090-180 [CLIPPER]
    _Rejected_ -> Junction_7
Junction_7
    -> Junction_8
Stoepbreedtebepaler_090
    GROUP_BY = segmentID STRAATCODE
    STOEPBREEDTE = 0.90
    Area -> Clipper_090-180 [CLIPPEE]
    Area -> Clipper_lt_090 [CLIPPER]
    _Rejected_ -> Junction_9
Junction_9
    -> Junction_10

Bookmark: trottoirbreedtes
AttributeCreator_gt_360
    ATTR_TABLE = SET_TO breedteklasse = > 3.60
    -> AttributeCreator_lt_090_OUTPUT_-__voetgangerwegdeelbreedtes
AttributeCreator_290-360
    ATTR_TABLE = SET_TO breedteklasse = 2.90 - 3.60
    -> AttributeCreator_lt_090_OUTPUT_-__voetgangerwegdeelbreedtes
AttributeCreator_220-290
    ATTR_TABLE = SET_TO breedteklasse = 2.20 - 2.90
    -> AttributeCreator_lt_090_OUTPUT_-__voetgangerwegdeelbreedtes
AttributeCreator_180-220
    ATTR_TABLE = SET_TO breedteklasse = 1.80 - 2.20
    -> AttributeCreator_lt_090_OUTPUT_-__voetgangerwegdeelbreedtes
AttributeCreator_090-180
    ATTR_TABLE = SET_TO breedteklasse = 0.90 - 1.80
    -> AttributeCreator_lt_090_OUTPUT_-__voetgangerwegdeelbreedtes
AttributeCreator_lt_090
    ATTR_TABLE = SET_TO breedteklasse = < 0.90
    -> AttributeCreator_lt_090_OUTPUT_-__voetgangerwegdeelbreedtes
AttributeCreator_lt_090_OUTPUT_-__voetgangerwegdeelbreedtes: Junction
    -> stoepbreedtes_bruto (writer GEOPACKAGE_2)

Bookmark: verwijderen van overlap
Clipper_290-360
    CREATE_AGGREGATES = Yes
    LINES_AS_SEGMENTS = No
    GROUP_BY = segmentID STRAATCODE
    VAL_SOURCE = Clippee Only
    MEASURE_TYPE = Continuous
    PRESERVE_CLIPPEE_EXTENTS = No
    CLIP_TYPE = Multiple Clippers
    BOUNDARY_CASES = Treat as Inside
    MISSING_VAL_MODE = Compute
    OUTSIDE -> AttributeCreator_290-360
    <REJECTED> -> Junction_19
Junction_19
    -> Junction_20
Clipper_220-290
    CREATE_AGGREGATES = Yes
    LINES_AS_SEGMENTS = No
    GROUP_BY = segmentID STRAATCODE
    VAL_SOURCE = Clippee Only
    MEASURE_TYPE = Continuous
    PRESERVE_CLIPPEE_EXTENTS = No
    CLIP_TYPE = Multiple Clippers
    BOUNDARY_CASES = Treat as Inside
    MISSING_VAL_MODE = Compute
    OUTSIDE -> AttributeCreator_220-290
    <REJECTED> -> Junction_17
Junction_17
    -> Junction_18
Clipper_180-220
    CREATE_AGGREGATES = Yes
    LINES_AS_SEGMENTS = No
    GROUP_BY = segmentID STRAATCODE
    VAL_SOURCE = Clippee Only
    MEASURE_TYPE = Continuous
    PRESERVE_CLIPPEE_EXTENTS = No
    CLIP_TYPE = Multiple Clippers
    BOUNDARY_CASES = Treat as Inside
    MISSING_VAL_MODE = Compute
    OUTSIDE -> AttributeCreator_180-220
    <REJECTED> -> Junction_15
Junction_15
    -> Junction_16
Clipper_090-180
    CREATE_AGGREGATES = Yes
    LINES_AS_SEGMENTS = No
    GROUP_BY = segmentID STRAATCODE
    VAL_SOURCE = Clippee Only
    MEASURE_TYPE = Continuous
    PRESERVE_CLIPPEE_EXTENTS = No
    CLIP_TYPE = Multiple Clippers
    BOUNDARY_CASES = Treat as Inside
    MISSING_VAL_MODE = Compute
    OUTSIDE -> AttributeCreator_090-180
    <REJECTED> -> Junction_13
Junction_13
    -> Junction_14
Clipper_lt_090
    CREATE_AGGREGATES = Yes
    LINES_AS_SEGMENTS = No
    GROUP_BY = segmentID STRAATCODE
    VAL_SOURCE = Clippee Only
    MEASURE_TYPE = Continuous
    PRESERVE_CLIPPEE_EXTENTS = No
    CLIP_TYPE = Multiple Clippers
    BOUNDARY_CASES = Treat as Inside
    MISSING_VAL_MODE = Compute
    OUTSIDE -> AttributeCreator_lt_090
    <REJECTED> -> Junction_11
Junction_11
    -> Junction_12

Bookmark: resultaat
stoepbreedtes_bruto (writer GEOPACKAGE_2)
    attributes: STRAATCODE text(16), segmentID int, breedteklasse text(20)
voetgangerswegdelen_indicatoren (writer GEOPACKAGE_2)
    attributes: STRAATCODE text(16), segmentID int, LENGTE int, aant_bomen int, aant_bomen_hm float, aant_banken int, aant_banken_hm float, aant_voordeuren int, aant_voordeuren_hm float

FME custom transformer Stoepbreedtebepaler

Parameters:
- GROUP_BY = STRAATCODE   # " " Group By
- STOEPBREEDTE = 3.60   # Stoepbreedte (m)

Area (input)
    -> Bufferer_neg
Bufferer_neg
    GROUP_BY = $(GROUP_BY)
    ANGLE = 22.5
    CORNER_STYLE = Round
    OFFSET = -1 * ($(STOEPBREEDTE)/2)
    CAP_STYLE = Round
    BUFFERED -> Deaggregator
    <REJECTED> -> Area_TooSmall (output)
Deaggregator
    SPLIT_COMPOSITES = No
    LIST_ATTR_MODE_LOOKUP = LEAN
    MODE = Flatten One Level
    EXPLODE_INSTANCES = No
    DEAGGREGATED -> Bufferer_pos
Bufferer_pos
    GROUP_BY = $(GROUP_BY)
    ANGLE = 22.5
    CORNER_STYLE = Round
    OFFSET = $(STOEPBREEDTE)/2
    CAP_STYLE = Round
    BUFFERED -> Dissolver_buffers
    <REJECTED> -> _Rejected_ (output)
Dissolver_buffers
    GROUP_BY = $(GROUP_BY)
    CONNECT_Z_MODE = First Wins
    DEAGGREGATE_INPUT = Yes
    ACCUM_INPUT_ATTRS = Use Attributes From One Feature
    NO_OVRLP = No
    AREA -> Area (output)
    <REJECTED> -> _Rejected_ (output)
Area (output)
_Rejected_ (output)
Area_TooSmall (output)
